module ietf-l3vpn-svc {
 namespace "urn:ietf:params:xml:ns:yang:ietf-l3vpn-svc";

 prefix l3vpn-svc;

 import ietf-inet-types {
  prefix inet;
 }

 import ietf-yang-types {
  prefix yang;
 }

 organization
  "IETF L3SM Working Group";

 contact
  "WG List: <mailto:l3sm@ietf.org>

  Editor:
   L3SM WG

  Chairs:
   Adrian Farrel, Qin Wu
  ";

 description
  "This YANG module defines a generic service configuration
  model for Layer 3 VPNs.  This model is common across all
  vendor implementations.";

 revision 2017-05-02 {
  description
   "- adds elements specific for L3VPN Provider
    - removes default statements causing problems to OpenDaylight
    - removes not used elements
    Changes were made by organization FRINX s.r.o.
    Contact <mailto:info@frinx.io>";
 }
 revision 2017-01-27 {
  description
   "Initial document.";
  reference
    "RFC 8049.";
 }

 /* Features */

 feature ipv4 {
  description
   "Enables IPv4 support in a VPN.";
 }

 feature rtg-bgp {
  description
   "Enables support of the BGP routing protocol.";
 }

 /* Typedefs */

 typedef svc-id {
  type string;
  description
   "Defines a type of service component identifier.";
 }

 typedef address-family {
  type enumeration {
   enum ipv4 {
    description
     "IPv4 address family.";
   }
   enum ipv6 {
    description
     "IPv6 address family.";
   }
  }
  description
   "Defines a type for the address family.";
 }

 /* Identities */

 identity site-network-access-type {
  description
   "Base identity for site-network-access type.";
 }
 identity multipoint {
  base site-network-access-type;
  description
   "Identity for multipoint connection.
   Example: Ethernet broadcast segment.";
 }

 identity site-vpn-flavor {
  description
   "Base identity for the site VPN service flavor.";
 }
 identity site-vpn-flavor-single {
  base site-vpn-flavor;
  description
   "Base identity for the site VPN service flavor.
   Used when the site belongs to only one VPN.";
 }

 identity management {
  description
   "Base identity for site management scheme.";
 }
 identity customer-managed {
  base management;
  description
   "Base identity for customer-managed site.";
 }

 identity address-allocation-type {
  description
   "Base identity for address-allocation-type for PE-CE link.";
 }
 identity static-address {
  base address-allocation-type;
  description
   "Provider-to-customer addressing is static.";
 }

 identity site-role {
  description
   "Base identity for site type.";
 }
 identity any-to-any-role {
  base site-role;
  description
   "Site in an any-to-any IP VPN.";
 }

 identity vpn-topology {
  description
   "Base identity for VPN topology.";
 }
 identity any-to-any {
  base vpn-topology;
  description
   "Identity for any-to-any VPN topology.";
 }

 identity routing-protocol-type {
  description
   "Base identity for routing protocol type.";
 }
 identity bgp {
  base routing-protocol-type;
  description
   "Identity for BGP protocol type.";
 }

 /* Groupings */

 grouping site-routing {
  container routing-protocols {
   list routing-protocol {
    key type;

    leaf type {
     type identityref {
      base routing-protocol-type;
     }
     description
      "Type of routing protocol. Only bgp is supported.";
    }

    container bgp {

     when "../type = 'bgp'" {
      description
       "Only applies when protocol is BGP.";
     }
     if-feature rtg-bgp;
     leaf autonomous-system {
      type uint32;
      description
       "AS number.";
     }
     leaf-list address-family {
      type address-family;

      description
       "Address family to be activated.";
     }
     description
      "BGP-specific configuration.";
    }
    description
     "List of routing protocols used on
     the site.  This list can be augmented.";
   }
   description
    "Defines routing protocols.";
  }
  description
   "Grouping for routing protocols.";
 }

 grouping site-attachment-ip-connection {
  container ip-connection {
   container ipv4 {
    if-feature ipv4;
    leaf address-allocation-type {
     type identityref {
      base address-allocation-type;
     }
     default "static-address";
     description
      "Defines how addresses are allocated. Only static-address is supported.";
    }

    container addresses {
     when "../address-allocation-type = 'static-address'" {
      description
       "Only applies when protocol allocation type is static.";
     }
     leaf provider-address {
      type inet:ipv4-address;
      description
       "Address of provider side.";
     }
     leaf customer-address {
      type inet:ipv4-address;
      description
       "Address of customer side.";
     }
     leaf mask {
      type uint8 {
       range "0..31";
      }
      description
       "Subnet mask expressed in bits.";
     }
     description
      "Describes IP addresses used.";
    }

    description
     "IPv4-specific parameters.";

   }
   description
    "Defines connection parameters.";
  }
  description
   "This grouping defines IP connection parameters.";
 }

 grouping site-management {
  container management {
   leaf type {
    type identityref {
     base management;
    }
    description
     "Management type of the connection. Only customer-managed is supported.";
   }
   description
    "Management configuration.";
  }
  description
   "Management parameters for the site.";
 }

 grouping site-vpn-flavor-fields {
  leaf site-vpn-flavor {
   type identityref {
    base site-vpn-flavor;
   }
   default site-vpn-flavor-single;
   description
    "Defines whether the site is, for example,
    a single VPN site or a multiVPN. Only site-vpn-flavor-single is supported.";
  }
  description
   "Grouping for site VPN flavor.";
 }

 grouping access-vpn-policy {
  container vpn-attachment {

   choice attachment-flavor {
    case vpn-id {
     leaf vpn-id {
      type leafref {
       path "/l3vpn-svc/vpn-services"+
       "/vpn-service/vpn-id";
      }
      description
       "Reference to a VPN.";
     }
     leaf site-role {
      type identityref {
        base site-role;
       }
      default any-to-any-role;
      description
       "Role of the site in the IP VPN. Only any-to-any-role is supported.";
     }
    }
    mandatory true;
    description
     "Choice for VPN attachment flavor.";
   }
   description
    "Defines VPN attachment of a site.";
  }
  description
   "Defines the VPN attachment rules for a site's logical access.";
 }

 grouping vpn-svc-cfg {
  leaf vpn-id {
    type svc-id;
    description
     "VPN identifier.  Local administration meaning.";
   }
   leaf customer-name {
    type string;
    description
     "Name of the customer.";
   }
  leaf vpn-service-topology {
   type identityref {
    base vpn-topology;
   }
   default "any-to-any";
   description
    "VPN service topology.";
  }

  description
   "Grouping for VPN service configuration.";
 }

 grouping site-top-level-cfg {
  uses site-management;
  uses site-vpn-flavor-fields;

  description
   "Grouping for site top-level configuration.";
 }

 grouping site-network-access-top-level-cfg {
  leaf site-network-access-type {
   type identityref {
    base site-network-access-type;
   }
   default "multipoint";
   description
    "Describes the type of connection, e.g.,
    point-to-point or multipoint. Only multipoint is supported.";
  }

  uses site-attachment-ip-connection;
  uses site-routing;
  uses access-vpn-policy;

  description
   "Grouping for site network access top-level configuration.";
 }

 grouping l3vpn-svc-fields {
  container vpn-services {
   list vpn-service {
    key vpn-id;

    uses vpn-svc-cfg;

    description
     "List of VPN services.";
   }
   description
    "Top-level container for the VPN services.";
  }

  container sites {
   list site {
    key site-id;

    leaf site-id {
     type svc-id;
     description
      "Identifier of the site.";
    }

    uses site-top-level-cfg;
    container site-network-accesses {
     list site-network-access {
      key site-network-access-id;

      leaf site-network-access-id {
       type svc-id;
       description
        "Identifier for the access.";
      }
      uses site-network-access-top-level-cfg;

      description
       "List of accesses for a site.";
     }
     description
      "List of accesses for a site.";
    }

    description
     "List of sites.";
   }
   description
    "Container for sites.";
  }
 }

 /* Main blocks */
 container l3vpn-svc {
  presence true;
  uses l3vpn-svc-fields;
  description
   "Main container for L3VPN service configuration.";
 }

  //
  /* Used by L3VPN Provider */
  //

  typedef status {
    description "A type describing the status of L3VPN processing by provider.";
    type enumeration {
      enum in-progress {
        value 0;
        description "L3VPN processing is in progress.";
      }
      enum complete {
        value 1;
        description "L3VPN processing completed successfully.";
      }
      enum rollback-in-progress {
        value 2;
        description "L3VPN processing did not complete successfully and therefore
                rollback is in progress.";
      }
      enum failed {
        value -1;
        description "L3VPN processing did not complete successfully and rollback completed
                successfully.";
      }
      enum inconsistent {
        value -2;
        description "L3VPN processing and rollback did not complete successfully.";
      }
    }
  }

  grouping version-fields {
    leaf l3vpn-svc-version {
      mandatory true;
      type string;
    }
  }

  container status-l3vpn-provider {
    config false;
    container provider-state {
      leaf status {
        mandatory true;
        type status;
      }
      uses version-fields;
    }
    container processed-l3vpn-svc {
      uses l3vpn-svc-fields;
      description "L3VPN service which is processed or was processed.";
    }
  }

  container configured-l3vpn-svc {
    config false;
    uses version-fields;
    uses l3vpn-svc-fields;
    description "Current, successfully configured L3VPN service.";
  }

  rpc commit-l3vpn-svc {
    description "Reads l3vpn-svc from config datastore, assigns version, and starts network
        element configuration. Output is returned immediately after processing of intended l3vpn-svc started.
        A progress of configuration can be found in root container status-l3vpn-provider.";
    output {
      uses version-fields;
    }
  }

}
